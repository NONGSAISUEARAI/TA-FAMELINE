;Effective Block Name Funcition Lee Mac
  ;; Effective Block Name  -  Lee Mac
    ;; obj - [vla] VLA Block Reference object
  (defun LM:effectivename (obj) 
    (vlax-get-property obj 
                      (if (vlax-property-available-p obj 'effectivename) 
                        'effectivename
                        'name
                      )
    )
  )
  ;; Effective Block Name  -  Lee Mac
  ;; ent - [ent] Block Reference entity
  (defun LM:al-effectivename (ent / blk rep) 
    (if (wcmatch (setq blk (cdr (assoc 2 (entget ent)))) "`**") 
      (if 
        (and 
          (setq rep (cdadr 
                      (assoc -3 
                            (entget 
                              (cdr 
                                (assoc 330 
                                        (entget 
                                          (tblobjname "block" blk)
                                        )
                                )
                              )
                              '("AcDbBlockRepBTag")
                            )
                      )
                    )
          )
          (setq rep (handent (cdr (assoc 1005 rep))))
        )
        (setq blk (cdr (assoc 2 (entget rep))))
      )
    )
    blk
  )

;
;Attribute Function Lee Mac
  ;; Get Attribute Value  -  Lee Mac
  ;; Returns the value held by the specified tag within the supplied block, if present.
  ;; blk - [vla] VLA Block Reference Object
  ;; tag - [str] Attribute TagString
  ;; Returns: [str] Attribute value, else nil if tag is not found.
  (defun LM:vl-getattributevalue (blk tag) 
    (setq tag (strcase tag))
    (vl-some 
      '(lambda (att) 
        (if (= tag (strcase (vla-get-tagstring att))) (vla-get-textstring att))
      )
      (vlax-invoke blk 'getattributes)
    )
  )
  ;; Set Attribute Value  -  Lee Mac
  ;; Sets the value of the first attribute with the given tag found within the block, if present.
  ;; blk - [vla] VLA Block Reference Object
  ;; tag - [str] Attribute TagString
  ;; val - [str] Attribute Value
  ;; Returns: [str] Attribute value if successful, else nil.
  (defun LM:vl-setattributevalue (blk tag val) 
    (setq tag (strcase tag))
    (vl-some 
      '(lambda (att) 
        (if (= tag (strcase (vla-get-tagstring att))) 
          (progn (vla-put-textstring att val) val)
        )
      )
      (vlax-invoke blk 'getattributes)
    )
  )
  ;; Get Attribute Values  -  Lee Mac
  ;; Returns an association list of attributes present in the supplied block.
  ;; blk - [vla] VLA Block Reference Object
  ;; Returns: [lst] Association list of ((<tag> . <value>) ... )
  (defun LM:vl-getattributevalues (blk) 
    (mapcar '(lambda (att) (cons (vla-get-tagstring att) (vla-get-textstring att))) 
            (vlax-invoke blk 'getattributes)
    )
  )
  (defun LM:vl-getattributevalue-tag-TA-Modifies (blk) 
    (mapcar '(lambda (att) (vla-get-tagstring att)) 
            (vlax-invoke blk 'getattributes)
    )
  )
  (defun LM:vl-getattributevalue-val-TA-Modifies (blk) 
    (mapcar '(lambda (att) (vla-get-textstring att)) 
            (vlax-invoke blk 'getattributes)
    )
  )
  ;; Set Attribute Values  -  Lee Mac
  ;; Sets attributes with tags found in the association list to their associated values.
  ;; blk - [vla] VLA Block Reference Object
  ;; lst - [lst] Association list of ((<tag> . <value>) ... )
  ;; Returns: nil
  (defun LM:vl-setattributevalues (blk lst / itm) 
    (foreach att (vlax-invoke blk 'getattributes) 
      (if (setq itm (assoc (vla-get-tagstring att) lst)) 
        (vla-put-textstring att (cdr itm))
      )
    )
  )
;
;Dynamic Funcion Lee Mac
  ;; Get Dynamic Block Property Value  -  Lee Mac
    ;; Returns the value of a Dynamic Block property (if present)
    ;; blk - [vla] VLA Dynamic Block Reference object
    ;; prp - [str] Dynamic Block property name (case-insensitive)

    (defun LM:getdynpropvalue ( blk prp )
        (setq prp (strcase prp))
        (vl-some '(lambda ( x ) (if (= prp (strcase (vla-get-propertyname x))) (vlax-get x 'value)))
            (vlax-invoke blk 'getdynamicblockproperties)
        )
    )
  ;; Set Dynamic Block Property Value  -  Lee Mac
    ;; Modifies the value of a Dynamic Block property (if present)
    ;; blk - [vla] VLA Dynamic Block Reference object
    ;; prp - [str] Dynamic Block property name (case-insensitive)
    ;; val - [any] New value for property
    ;; Returns: [any] New value if successful, else nil

    (defun LM:setdynpropvalue ( blk prp val )
        (setq prp (strcase prp))
        (vl-some
          '(lambda ( x )
                (if (= prp (strcase (vla-get-propertyname x)))
                    (progn
                        (vla-put-value x (vlax-make-variant val (vlax-variant-type (vla-get-value x))))
                        (cond (val) (t))
                    )
                )
            )
            (vlax-invoke blk 'getdynamicblockproperties)
        )
    )
  ;; Get Dynamic Block Properties  -  Lee Mac
    ;; Returns an association list of Dynamic Block properties & values.
    ;; blk - [vla] VLA Dynamic Block Reference object
    ;; Returns: [lst] Association list of ((<prop> . <value>) ... )

    (defun LM:getdynprops ( blk )
        (mapcar '(lambda ( x ) (cons (vla-get-propertyname x) (vlax-get x 'value)))
            (vlax-invoke blk 'getdynamicblockproperties)
        )
    )
  ;; Set Dynamic Block Properties  -  Lee Mac
    ;; Modifies values of Dynamic Block properties using a supplied association list.
    ;; blk - [vla] VLA Dynamic Block Reference object
    ;; lst - [lst] Association list of ((<Property> . <Value>) ... )
    ;; Returns: nil

    (defun LM:setdynprops ( blk lst / itm )
        (setq lst (mapcar '(lambda ( x ) (cons (strcase (car x)) (cdr x))) lst))
        (foreach x (vlax-invoke blk 'getdynamicblockproperties)
            (if (setq itm (assoc (strcase (vla-get-propertyname x)) lst))
                (vla-put-value x (vlax-make-variant (cdr itm) (vlax-variant-type (vla-get-value x))))
            )
        )
    )
  ;; Get Dynamic Block Property Allowed Values  -  Lee Mac
    ;; Returns the allowed values for a specific Dynamic Block property.
    ;; blk - [vla] VLA Dynamic Block Reference object
    ;; prp - [str] Dynamic Block property name (case-insensitive)
    ;; Returns: [lst] List of allowed values for property, else nil if no restrictions

    (defun LM:getdynpropallowedvalues ( blk prp )
        (setq prp (strcase prp))
        (vl-some '(lambda ( x ) (if (= prp (strcase (vla-get-propertyname x))) (vlax-get x 'allowedvalues)))
            (vlax-invoke blk 'getdynamicblockproperties)
        )
    )
  ;; Toggle Dynamic Block Flip State  -  Lee Mac
    ;; Toggles the Flip parameter if present in a supplied Dynamic Block.
    ;; blk - [vla] VLA Dynamic Block Reference object
    ;; Return: [int] New Flip Parameter value

    (defun LM:toggleflipstate ( blk )
        (vl-some
          '(lambda ( prp / rtn )
                (if (equal '(0 1) (vlax-get prp 'allowedvalues))
                    (progn
                        (vla-put-value prp (vlax-make-variant (setq rtn (- 1 (vlax-get prp 'value))) vlax-vbinteger))
                        rtn
                    )
                )
            )
            (vlax-invoke blk 'getdynamicblockproperties)
        )
    )
  ;; Get Visibility Parameter Name  -  Lee Mac
    ;; Returns the name of the Visibility Parameter of a Dynamic Block (if present)
    ;; blk - [vla] VLA Dynamic Block Reference object
    ;; Returns: [str] Name of Visibility Parameter, else nil

    (defun LM:getvisibilityparametername ( blk / vis )  
        (if
            (and
                (vlax-property-available-p blk 'effectivename)
                (setq blk
                    (vla-item
                        (vla-get-blocks (vla-get-document blk))
                        (vla-get-effectivename blk)
                    )
                )
                (= :vlax-true (vla-get-isdynamicblock blk))
                (= :vlax-true (vla-get-hasextensiondictionary blk))
                (setq vis
                    (vl-some
                      '(lambda ( pair )
                            (if
                                (and
                                    (= 360 (car pair))
                                    (= "BLOCKVISIBILITYPARAMETER" (cdr (assoc 0 (entget (cdr pair)))))
                                )
                                (cdr pair)
                            )
                        )
                        (dictsearch
                            (vlax-vla-object->ename (vla-getextensiondictionary blk))
                            "ACAD_ENHANCEDBLOCK"
                        )
                    )
                )
            )
            (cdr (assoc 301 (entget vis)))
        )
    )
  ;; Get Dynamic Block Visibility State  -  Lee Mac
    ;; Returns the value of the Visibility Parameter of a Dynamic Block (if present)
    ;; blk - [vla] VLA Dynamic Block Reference object
    ;; Returns: [str] Value of Visibility Parameter, else nil

    (defun LM:getvisibilitystate ( blk / vis )
        (if (setq vis (LM:getvisibilityparametername blk))
            (LM:getdynpropvalue blk vis)
        )
    )
  ;; Set Dynamic Block Visibility State  -  Lee Mac
    ;; Sets the Visibility Parameter of a Dynamic Block (if present) to a specific value (if allowed)
    ;; blk - [vla] VLA Dynamic Block Reference object
    ;; val - [str] Visibility State Parameter value
    ;; Returns: [str] New value of Visibility Parameter, else nil

    (defun LM:SetVisibilityState ( blk val / vis )
        (if
            (and
                (setq vis (LM:getvisibilityparametername blk))
                (member (strcase val) (mapcar 'strcase (LM:getdynpropallowedvalues blk vis)))
            )
            (LM:setdynpropvalue blk vis val)
        )
    )
;
;Remove List Function Lee Mac
  (defun LM:RemoveNth (n l / i) 
    ;;  Arguments:                                              ;;
    ;;  n - index of item to remove (zero based)                ;;
    ;;  l - list from which item is to be removed               ;;
      (setq i -1)
      (vl-remove-if '(lambda (x) (= (setq i (1+ i)) n)) l)
  )
;
;Method Selection Set Ta Trai
  (defun TA:standard_func_selection_set_cond_case_1 () ;วิธีเก็บข้อมูล selection set แบบเดียวกับ pickfirst variable
    ;selection_set
      (if  ;pre_select_ssget_or_post_select_ssget
        (= 
          (setq ss_pre_filter_set_xx (ssget "I" 
                                            (list 
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn 
          (setq ss_pre_filter_set_xx (ssget 
                                        (list 
                                          (cons 0 "INSERT") ;type of object
                                          ; (cons 8 "000 - GRID")   ;kind of layer
                                          ; (cons 2 "000-GRIDLINE_DYN")       ;kind of nameblock
                                          ; (cons 62 1)           ;kind of color call sign with color code index
                                        )
                                      )
          )
        )
        (sslength ss_pre_filter_set_xx)
      )
    ;
  )
  (defun TA:standard_func_entsel_case_1 () ;วิธีเก็บข้อมูลแบบตัวแปรเดี่ยวตามเงื่อนไข (condition rule) จนกว่าจะถูกต้อง
    ;user_input get_effectivename 
      (setq get_effectivename_ nil)
      (setq get_effectivename_obj_val_ nil)
      ;preloop_and_while_
          (while (not get_effectivename_)
            (princ (setq get_effectivename_ (car (entsel "\nPlease Specify Attribute Block\n"))))
            (if (and ;condition rule
                  (/= get_effectivename_ nil)
                  (= (vla-get-hasattributes (vlax-ename->vla-object get_effectivename_)) :vlax-true)
                  ; (/= (vla-get-isdynamicblock (vlax-ename->vla-object get_effectivename_)) :vlax-true)
                )
              (progn ;add data
                ; (alert "\nplease select block object")
                ; (setq get_effectivename_ nil)
                ; (setq get_effectivename_obj_val_ nil)
                (setq get_effectivename_obj_val_ (LM:Effectivename (vlax-ename->vla-object get_effectivename_)))
                ;add more
              )
              (setq get_effectivename_ nil)
            )
          )
      ;
    ;
    ;user_input_get_block_(not loop)
      ;block_data_for insertion
        (setq blk_ename_ (car (entsel "specify_block_")))
        (setq blk_ename_obj_ (vlax-ename->vla-object blk_ename_))
        (if (= (setq type_obj_ (vla-get-objectname (vlax-ename->vla-object blk_ename_))) "AcDbBlockReference") ;For Check objectname
          (progn
            (setq blk_ename_obj_inspt_ (vlax-safearray->list (vlax-variant-value (vla-get-insertionpoint blk_ename_obj_))))
            (setq blk_ename_obj_efname_ (LM:effectivename blk_ename_obj_ ))
          )
          (alert "Object is not block.")
        )
      ;
    ;
    ;get_data_dynamic_block_object
      (if (= 1 1) 
        (progn
          ;user_input_get_block_(not loop)
            ;block_data_for insertion
              (if (/= (setq blk_ename_ (car (entsel "specify_block_"))) nil)
                (progn
                  (setq blk_ename_obj_ (vlax-ename->vla-object blk_ename_))
                )
                (alert "Object is blank.")
              )         
              (if (and
                    (= (setq type_obj_ (vla-get-objectname (vlax-ename->vla-object blk_ename_))) "AcDbBlockReference");For Check objectname
                    (= (vla-get-isdynamicblock blk_ename_obj_) :vlax-true );For Check objectname is dynamicblock
                  ) 
                (progn
                  (setq blk_ename_obj_inspt_ (vlax-safearray->list (vlax-variant-value (vla-get-insertionpoint blk_ename_obj_))))
                  (setq blk_ename_obj_efname_ (LM:effectivename blk_ename_obj_ ))
                )
                (alert "Object is not block.")
              )
            ;
          ;
        )
      )
    ;
  )
;
;Sorting Coordinate Function Ta Trai
  (defun CO:sort_by_X (list_)  ;เรียงชุดข้อมูลตามแนวแกน
    (setq sortedLst (vl-sort list_ (function (lambda (a b) (< (car (cadr a)) (car (cadr b)))))))
  )
  (defun CO:sort_by_y (list_)  ;เรียงชุดข้อมูลตามแนวแกน
    (setq sortedLst (vl-sort list_ (function (lambda (a b) (< (cadr (cadr a)) (cadr (cadr b)))))))
  )
  (defun CO:sort_by_val_ (val_ list_ )  ;เรียงชุดข้อมูลตามแนวแกน
    (if (< val_ (length (car list_)))
      (progn
        (setq sortedLst (vl-sort list_ (function (lambda (a b) (< (nth val_ a) (nth val_ b))))))
      )
      (setq error_ "The number of val is less than list")
    )
  )
;
;get_Intersect_func
  (defun LM:intersections (ob1 ob2 mod / lst rtn) 
    (if 
      (and (vlax-method-applicable-p ob1 'intersectwith) 
          (vlax-method-applicable-p ob2 'intersectwith)
          (setq lst (vlax-invoke ob1 'intersectwith ob2 mod))
      )
      (repeat (/ (length lst) 3) 
        (setq rtn (cons (list (car lst) (cadr lst) (caddr lst)) rtn)
              lst (cdddr lst)
        )
      )
    )
    (remove_member_list_ 2 (reverse rtn))
    
  )
  (defun LM:intersections+0 (ob1 ob2 mod / lst rtn) 
    (if 
      (and (vlax-method-applicable-p ob1 'intersectwith) 
          (vlax-method-applicable-p ob2 'intersectwith)
          (setq lst (vlax-invoke ob1 'intersectwith ob2 mod))
      )
      (repeat (/ (length lst) 3) 
        (setq rtn (cons (list (car lst) (cadr lst) (caddr lst)) rtn)
              lst (cdddr lst)
        )
      )
    )
    ; (remove_member_list_ 2 (reverse rtn))
    (reverse rtn)
    
  )
  (defun LM:intersections_crood_position (ob1 ob2 coord_ mod  / lst rtn) 
    (if 
      (and (vlax-method-applicable-p ob1 'intersectwith) 
          (vlax-method-applicable-p ob2 'intersectwith)
          (setq lst (vlax-invoke ob1 'intersectwith ob2 mod))
      )
      (repeat (/ (length lst) 3) 
        (setq rtn (cons (list (car lst) (cadr lst) (caddr lst)) rtn)
              lst (cdddr lst)
        )
      )
    )
    (cond ;soectify corrdinate position
      ((= coord_ "xyz")
      (progn 
        (reverse rtn)
      )
      )
      ((= coord_ "xy")
      (progn 
        (remove_member_list_ 2 (reverse rtn))
      )
      )
      ((or
        (/= coord_ "xy")
        (/= coord_ "xyz")
        (= coord_ nil)
       )
      (progn 
        (princ "\n:::::::::::::::: ERROR ::::::::::::::::::::::")
        (princ "\n:::::Please Specify Coordinate Position::::::\n")
        (princ ":::::::::::::: X Y    = 2 coord :::::::::::::\n")
        (princ ":::::::::::::: X Y Z  = 3 coord :::::::::::::\n")
      )
      )
    )
  )
;
;Filter Selection Set by Effectivename Ta Trai
  (defun TA:EF_Filter_ss_set_ (ss_pre_filter_set_  effectivename) ;กรอง block object ด้วย LM:effectivename
    (setq ss_post_filter_set_ (ssadd))
    ; (setq effectivename "12a")
    ;preloop_and_while
      (setq ss_pre_filter_set_i 0)
      (while 
        ;get_data
          (setq ss_pre_filter_set_ename (ssname  ss_pre_filter_set_ ss_pre_filter_set_i) )
          (setq ss_pre_filter_set_obj (vlax-ename->vla-object ss_pre_filter_set_ename))
          (setq ss_pre_filter_set_obj_efname_ (LM:effectivename ss_pre_filter_set_obj))
        ;
        ;filter_data
          (if (= ss_pre_filter_set_obj_efname_ effectivename)
            (progn
            (ssadd ss_pre_filter_set_ename ss_post_filter_set_)
            )
            (princ (strcat "\nfilter_selection_set_and_sorting is processing " (rtos (* ss_pre_filter_set_i (/ 100 (float (sslength ss_pre_filter_set_)))) 2 0) "%\n"))
          )
        ;
        (setq ss_pre_filter_set_i (+ ss_pre_filter_set_i 1))
      )
    ;
    (sslength ss_post_filter_set_)
    (princ ss_post_filter_set_)
    (setq ss_post_filter_set_ ss_post_filter_set_)
  )
  (defun TA:Prop_Filter_ss_set_ (Selection_list_ nameprop_ propval_)
    (setq temp_ssget_ (ssadd))
    (setq Selection_list_i 0)
    (while (< Selection_list_i (sslength Selection_list_))
      (setq Selection_list_ename_ (ssname Selection_list_ Selection_list_i))
      (setq Selection_list_obj_ (vlax-ename->vla-object Selection_list_ename_))
        (if
          (= (vlax-get-property Selection_list_obj_ nameprop_) propval_ )
          (progn
            (setq temp_ssget_ (ssadd Selection_list_ename_ temp_ssget_))
          )
          (princ "\n")
        )
      (setq Selection_list_i (+ Selection_list_i 1))
    )
    (sslength temp_ssget_)
    (setq temp_ssget_ temp_ssget_)
  )
  (defun TA:member (str_name_ member_list_)
      (setq member_list_i 0)
      (setq found nil)
      (while (and
              (< member_list_i (length member_list_))
              (/= found T)
            )
        (setq member_list_val (nth member_list_i member_list_))
        (if (= str_name_ member_list_val)
          (progn
            (setq found T)  
          )
            (setq found nil)
        )
        (setq member_list_i (+ member_list_i 1))
      )
      (setq result found)
  )
  (defun TA:member_position (str_name_ pos member_list_)
      (setq member_list_i 0)
      (setq result_found_val ())
      (setq found nil)
      (while (and
              (< member_list_i (length member_list_))
              ; (/= found T)
            )
        (setq member_list_val (nth member_list_i member_list_))
        (if (= str_name_ (nth pos member_list_val))
          (progn
            ; (setq found T)
            (setq result_found_val (cons member_list_val result_found_val))          
          )
            (setq found nil)
        )
        (setq member_list_i (+ member_list_i 1))
      )
      (setq result result_found_val)
  )
  (defun remove_member_list_ (num_ point_list_)
    (setq new_list_ ())
    ; (setq num_ 2)
    (setq point_list_i 0)
    (while (< point_list_i (length point_list_))
      
      (setq point_list_set_ (nth point_list_i point_list_))
      (setq point_list_set_remove (vl-remove (nth num_ point_list_set_) point_list_set_))
      (setq new_list_ (cons point_list_set_remove new_list_))
      (setq point_list_i (+ point_list_i 1))
      
    )
    (setq result_ (reverse new_list_))
  )
  (defun remove_single_list_ (num_ point_list_)
    (setq new_list_ ())
      (setq point_list_set_ point_list_)
      (setq point_list_set_remove (vl-remove (nth num_ point_list_set_) point_list_set_))

    (setq result_ point_list_set_remove)
  )
;
;Get_Data Document Ta Trai
  (defun LM:getdocumentobject ( dwg / app dbx dwl err vrs )
      (cond
          (   (not (setq dwg (findfile dwg))) nil)
          (   (cdr
                  (assoc (strcase dwg)
                      (vlax-for doc (vla-get-documents (setq app (vlax-get-acad-object)))
                          (setq dwl (cons (cons (strcase (vla-get-fullname doc)) doc) dwl))
                      )
                  )
              )
          )
          (   (progn
                  (setq dbx
                      (vl-catch-all-apply 'vla-getinterfaceobject
                          (list app
                              (if (< (setq vrs (atoi (getvar 'acadver))) 16)
                                  "objectdbx.axdbdocument"
                                  (strcat "objectdbx.axdbdocument." (itoa vrs))
                              )
                          )
                      )
                  )
                  (or (null dbx) (vl-catch-all-error-p dbx))
              )
              (prompt "\nUnable to interface with ObjectDBX.")
          )
          (   (vl-catch-all-error-p (setq err (vl-catch-all-apply 'vla-open (list dbx dwg))))
              (prompt (strcat "\n" (vl-catch-all-error-message err)))
          )
          (   dbx   )
      )
  )
  (defun getdrawinglayouts ( dwg / doc idx rtn )
    ;original_method_
      (if (setq doc (LM:getdocumentobject dwg))
          (progn
              (vlax-for lyt (vla-get-layouts doc)
                  (setq rtn (cons (vla-get-name lyt) rtn)
                        idx (cons (vla-get-taborder lyt) idx)
                  )
              )
              (vlax-release-object doc)
              (mapcar '(lambda ( n ) (nth n rtn)) (vl-sort-i idx '<))
          )
      )
    ;
  )
;
;Get_Data Function Ta Trai
  (defun TA:get_name_block_in_drawing (mode)
    ;user_input_
      (setq mode "mode")
    ;
    ;get_obj_file_
      (setq multi_blocks_obj (vla-get-blocks (vla-get-ActiveDocument (vlax-get-acad-object))))
      (setq block_list_ ())
    ;
    ;method_for_get_name_block_in_drawing
      ;method_1_get_name_
        (vlax-for block_ multi_blocks_obj 
          (setq block_list_ (append block_list_ (list (vla-get-name block_))))
        )
      ;
      ; ;method_2_get_name_
      ;   (setq block_i 0)
      ;   (while (< block_i (vla-get-count multi_blocks_obj))
      ;     (setq block_ (vla-item multi_blocks_obj block_i))
      ;     (setq block_list_ (append block_list_ (list (vla-get-name block_))))
      ;     (setq block_i (1+ block_i))
      ;   )
      ; ;
    ;
    ;sorting_name_block
      (setq sorted_block_list_ (acad_strlsort block_list_))
    ;
    ;preloop_and_while filtter_
      (setq sorted_block_list_i 0)
      (setq filter_sorted_block_ ())

      (while (< sorted_block_list_i (length sorted_block_list_))
        (setq filter_sorted_block_effectivename_ (nth sorted_block_list_i sorted_block_list_))
        
        (if (/= (substr filter_sorted_block_effectivename_ 1 1) "*") ; ตรวจสอบว่าชื่อเริ่มต้นด้วย *
          (progn
            (setq filter_sorted_block_ (cons filter_sorted_block_effectivename_ filter_sorted_block_))
          )
        )
        (setq sorted_block_list_i (+ sorted_block_list_i 1))
      )
    ;

    
    (setq filter_sorted_block_total (length filter_sorted_block_))
    (princ "\n                  |=====================|")
    (princ "\n                  | TOTAL BLOCK IN FILE |")
    (princ (strcat "\n                  |     = " (itoa filter_sorted_block_total) " block     |"))
    (princ "\n                  |          set        |")
    (princ "\n                  |---------------------|\n")
    (setq filter_sorted_block_ filter_sorted_block_)

  )
  (defun TA:get_name_layer_in_drawing ()
    (setq layers_list_ ())
    (setq layers_obj (vla-get-layers (vla-get-ActiveDocument (vlax-get-acad-object))))
    ;method_1_get_layers_name
      (vlax-for lay layers_obj
        (setq layers_list (append layers_list (list (vla-get-Name lay))))
      )
    ;
    ;method_2_get_layers_name
      (setq layers_i 0)
      (while (< layers_i (vla-get-count layers_obj))
        (setq layers_ (vla-item layers_obj layers_i))
        (setq layers_list_ (append layers_list_ (list (vla-get-name layers_))))
        (setq layers_i (1+ layers_i))
      )
    ;
    ;summary_layer_data
      (setq layers_list_total (length layers_list_))
      (princ "\n                  |=====================|")
      (princ "\n                  | TOTAL LAYERS IN FILE |")
      (princ (strcat "\n                  |     = " (itoa layers_list_total) " layer     |"))
      (princ "\n                  |          set        |")
      (princ "\n                  |---------------------|")
      (setq layers_list_ layers_list_)
    ;
  )
  (defun TA:ename+vla-get-insertionpoint (obj) ;ประกอบ entity_name กับ insertion_poiint ให้เป็น list (BLOCK ONLY)
    (if (= (vla-get-objectname obj) "AcDbBlockReference")
      (progn
        ;get_data
          (setq ename_ (vlax-vla-object->ename obj)) 
          
          (setq _inspt (vlax-safearray->list (vlax-variant-value (vla-get-insertionpoint obj))))
        ;
        ;sum_data_to_list
          (setq sum_list (list 
                          ename_
                          _inspt
                          ;add more
                        )
          )
        ;
      )
      (setq error "OBJECT IS NOT BLOCK")
    )
  )
  (defun TA:ename+vla-getboundingbox (obj) ;ประกอบ entity_name กับ vla-getboundingbox ให้เป็น list (LINE OR POLYLINE ONLY)
    ; (setq obj (vla-get-objectname (vlax-ename->vla-object (car (entsel))))) ;For Check objectname
    (if (or
          (= (vla-get-objectname obj) "AcDbLine")
          (= (vla-get-objectname obj) "AcDbPolyline")
          (= (vla-get-objectname obj) "AcDbBlockReference")
        )
      (progn
        ;get_data
          (setq ename_ (vlax-vla-object->ename obj)) 
          
          (setq _inspt (vla-getboundingbox obj 'min_ 'max_))
          (setq min_ (vlax-safearray->list min_))
          (setq max_ (vlax-safearray->list max_))
        ;
        ;sum_data_to_list
          (setq sum_list (list 
                           ename_
                           min_
                           max_
                           ;add more
                         )
          )
        ;
      )
      (setq error "OBJECT IS NOT LINE/POLYLINE")
    )
  )
  (defun TA:Get_Pline_vertext_angle_case1 (ename_) 
    (setq s_ (cadr (TA:Get_Pline_vertext_ins_point_ ename_)))
    (setq d1 (angtos (angle (nth 1 s_) (nth 2 s_))))
    (setq s_i 0)
    (setq s_ii 1)
    (setq end_val_ nil)
    (setq sum_ ())
    (while (< s_i (length s_))
        (setq pt_1 (nth s_i s_))
        (setq pt_3 (nth s_i s_))
        (if (= s_ii (length s_)) 
          (progn 
            (setq end_val_ "end")
            (setq pt_3 (nth (- s_i 1) s_))
          )
          (setq pt_2 (nth s_ii s_))
        )
        (setq angle_pt (atof (angtos (angle pt_1 pt_2))))
        (if (= end_val_ "end") 
          (progn
            (setq angle_pt (atof (angtos (angle pt_3 pt_1))))
            (setq sum (append  (list pt_1) (list angle_pt s_ii) ))
          )
          (setq sum (append  (list pt_1) (list angle_pt s_ii)))
        )
        
        (setq sum_ (cons sum sum_))
        (setq s_i (+ s_i 1))
        (setq s_ii (+ s_ii 1))
    )
    (setq result_ (reverse sum_))
  )
  (defun TA:Get_Pline_vertext_angle_case2 (ename_) 
    (setq s_ (cadr (TA:Get_Pline_vertext_ins_point_ ename_)))
    (setq d1 (angtos (angle (nth 1 s_) (nth 2 s_))))
    (setq s_i 0)
    (setq s_ii 1)
    (setq end_val_ nil)
    (setq sum_ ())
    (while (< s_i (length s_))
        (setq pt_1 (nth s_i s_))
        (if (= s_ii (length s_)) 
          (progn 
            (setq end_val_ "end")
          )
          (setq pt_2 (nth s_ii s_))
        )
        (setq angle_pt (atof (angtos (angle pt_1 pt_2))))
        (if (= end_val_ "end") 
          (progn 
            (setq sum (append  (list pt_1) (list end_val_ s_ii) ))
          )
          (setq sum (append  (list pt_1) (list angle_pt s_ii)))
        )
        
        (setq sum_ (cons sum sum_))
        (setq s_i (+ s_i 1))
        (setq s_ii (+ s_ii 1))
    )
    (setq result_ (reverse sum_))
  )
  (defun TA:Get_Pline_vertext_ins_point_ (ename_) ;must be (car (entsel))
    (setq Get_Pline_ (entget ename_))
    (setq Get_Pline_vtx_pt (vl-remove-if-not '(lambda (x) (= 10 (car x))) Get_Pline_))
    (setq Get_Pline_vtx_pt_ (mapcar 'cdr Get_Pline_vtx_pt))
    (setq ename+Get_Pline_vtx_pt_ (list
                                    ename_
                                    Get_Pline_vtx_pt_
                                  )
    
    )
  )
  (defun TA:get_vertex_len_ (ename_)
    ; (setq ref_line (car (entsel)))
    (setq ss (vlax-ename->vla-object ename_))
    (setq vertex_total (length (cadr (TA:Get_Pline_vertext_ins_point_ ename_))))
    (setq sum_ ())

    (setq vertex_i 0)
    (setq vertex_ii 1)

    (while (< vertex_i vertex_total)
      (cond
        (;_case_1
           (and
              (/= vertex_i (- vertex_total 1))
           )
           (progn
             ;get_data_len
              (setq len_i (vlax-curve-getDistatParam ss vertex_i) )
              (setq len_ii (vlax-curve-getDistatParam ss vertex_ii))
              ;
              ;sum
                (setq sum (list (- len_ii len_i)))
                (setq sum_ (append sum sum_ ))
              ;
             (princ "_case_1\n")
           )
        )
        (;_case_2
          (and
            (= vertex_i (- vertex_total 1))    
          )
          (progn
            ;ไม่มี
            (princ "_case_2\n")
          )
        )

      )
      
      
      (setq vertex_i (+ vertex_i 1))
      (setq vertex_ii (+ vertex_ii 1))
    )
    ;summary_reverse
      (setq sum_len (reverse sum_))
    ;
  )
  (defun TA:midpoint (ins_start_ ins_end_) ;คำนวณ midpoint จากระยะหัว-ท้าย ของเส้น
    ; (setq ins_start_ (list ins_start_x1 ins_start_y1))
    ; (setq ins_end_ (list ins_end_x1 ins_end_y1))
    (setq ins_mid_ (list 
                 (/ (+ (car ins_start_) (car ins_end_)) 2.0)
                 (/ (+ (cadr ins_start_) (cadr ins_end_)) 2.0)
               )
    )
  )
  (defun LM:PolyCentroid ( e / l )
    (foreach x (setq e (entget e))
        (if (= 10 (car x)) (setq l (cons (cdr x) l)))
    )
    (
        (lambda ( a )
            (if (not (equal 0.0 a 1e-8))
                (trans
                    (mapcar '/
                        (apply 'mapcar
                            (cons '+
                                (mapcar
                                    (function
                                        (lambda ( a b )
                                            (
                                                (lambda ( m )
                                                    (mapcar
                                                        (function
                                                            (lambda ( c d ) (* (+ c d) m))
                                                        )
                                                        a b
                                                    )
                                                )
                                                (- (* (car a) (cadr b)) (* (car b) (cadr a)))
                                            )
                                        )
                                    )
                                    l (cons (last l) l)
                                )
                            )
                        )
                        (list a a)
                    )
                    (cdr (assoc 210 e)) 0
                )
            )
        )
        (* 3.0
            (apply '+
                (mapcar
                    (function
                        (lambda ( a b )
                            (- (* (car a) (cadr b)) (* (car b) (cadr a)))
                        )
                    )
                    l (cons (last l) l)
                )
            )
        )
    )
  )
  (defun TA:find_center (main_border_) -
    (setq main_border_obj_ (vlax-ename->vla-object main_border_))
    (setq obj (vla-get-objectname main_border_obj_)) ;For Check objectname
    (if (= obj "AcDbPolyline") 
      (progn 
        (setq main_border_obj_boline_ (TA:ename+vla-getboundingbox main_border_obj_))
        (setq min_crood (cadr main_border_obj_boline_))
        (setq max_crood (caddr main_border_obj_boline_))
        (setq Mx (/ (+ (car min_crood) (car max_crood)) 2))
        (setq My (/ (+ (cadr min_crood) (cadr max_crood)) 2))
        (setq Mz (/ (+ (caddr min_crood) (caddr max_crood)) 2))
        (setq center_point_ (list Mx My Mz))
      )
      (alert "TA:find_center : Object is not PolyLine")
    )
  )
  (defun TA:Find_boundary_line_ (main_border_)
    ;for testing code
      ; (setq main_border_ (car (entsel)))
    ;
    ;get_data_
      (setq main_border_obj_ (vlax-ename->vla-object main_border_))
      (setq obj (vla-get-objectname main_border_obj_)) ;For Check objectname
      (if (or (= obj "AcDbPolyline") (= obj "AcDbBlockReference")) 
        (progn 
          (setq main_border_obj_boline_ (TA:ename+vla-getboundingbox main_border_obj_))
          (setq min_crood (cadr main_border_obj_boline_))
          (setq max_crood (caddr main_border_obj_boline_))
          ; (setq Mx (/ (+ (car min_crood) (car max_crood)) 2))
          ; (setq My (/ (+ (cadr min_crood) (cadr max_crood)) 2))
          ; (setq Mz (/ (+ (caddr min_crood) (caddr max_crood)) 2))
          ; (setq center_point_ (list Mx My Mz))
          (setq obj_boline_ (list 
                              (cadr main_border_obj_boline_ )
                              (caddr main_border_obj_boline_ )
                            )
          )
        )
        (alert "TA:find_center : Object is not PolyLine")
      )
    ;
  )
;
;Sorting_Selection_Set_by_Coordinate Ta Trai
  (defun TA:standard_list_croodinate_sorting (ss_post_filter_set_ sequence ) ;เรียง object ตามแนวแกน ใน selection set
    ; ;selection_set
      ;   (if  ;pre_select_ssget_or_post_select_ssget
      ;     (= 
      ;       (setq ss_pre_filter_set_xx (ssget "I" 
      ;                                         (list 
      ;                                           (cons 0 "INSERT") ;type of object
      ;                                           ; (cons 8 "000 - GRID")   ;kind of layer
      ;                                           ; (cons 2 "000-GRID_LINE_DYN")       ;kind of nameblock
      ;                                           ; (cons 62 1)           ;kind of color call sign with color code index
      ;                                         )
      ;                                   )
      ;       )
      ;       nil
      ;     )
      ;     (progn 
      ;       (setq ss_pre_filter_set_xx (ssget 
      ;                                     (list 
      ;                                       (cons 0 "INSERT") ;type of object
      ;                                       ; (cons 8 "000 - GRID")   ;kind of layer
      ;                                       ; (cons 2 "000-GRIDLINE_DYN")       ;kind of nameblock
      ;                                       ; (cons 62 1)           ;kind of color call sign with color code index
      ;                                     )
      ;                                   )
      ;       )
      ;     )
      ;     (sslength ss_pre_filter_set_xx)
      ;   )
    ; ;
    ; ;user_input
      ;   (setq effectivename_val (LM:effectivename (vlax-ename->vla-object (car (entsel )))))
    ; ;
    ; ;filter_via_sub_func
      ;   (setq ss_post_filter_set_ (TA:Filter_ss_set_ ss_pre_filter_set_xx  effectivename_val))
    ; ;
    ;preloop_and_while get_ename_and_add_ins_pt
      (setq sum_data_ ())
      (setq ss_post_filter_set_i 0)
      (while  (< ss_post_filter_set_i (sslength ss_post_filter_set_))
        ;get_data
          (setq ss_post_filter_set_ename (ssname ss_post_filter_set_ ss_post_filter_set_i))
          (setq ss_post_filter_set_obj (vlax-ename->vla-object ss_post_filter_set_ename))
        ;
        ;sum_data_via_data
          (setq sum_data (TA:ename+vla-get-insertionpoint ss_post_filter_set_obj))
          (setq sum_data_ (cons sum_data sum_data_))
        ;
        (setq ss_post_filter_set_i (+ ss_post_filter_set_i 1))
      )
    ;
    ;sub_user_input_
      (cond
        ((= sequence "X") ;correct case
          (progn
            (princ "XXX")
            (setq sort_x (CO:sort_by_X sum_data_))
          )
        )
        ((= sequence "Y") ;correct case
          (progn
            (princ "YYY")
            (setq sort_y (CO:sort_by_Y sum_data_))
          )
        )
        ((and ;incorrect case
            (/= sequence "X")
            (/= sequence "Y")
          )
          (progn
            (princ "error_sorting_ename please specify argument X or Y")
            ; (setq sort_y (sort_by_y sum_data_))
          )
        )
      )
    ;
  )
;
;convert_value_
  (defun deg-to-rad (angle)
    (* angle (/ pi 180.0))
  )
  (defun rad-to-deg (rad)
    (/ (* rad 180) pi) 
  )
  (defun LM:round ( n )
    (fix (+ n (if (minusp n) -0.5 0.5)))
  )
  (defun relocate_ins_ (data_list_ x_sym x_num_ y_sym y_num_ )
    (if (= (length data_list_) 2)
      (progn
        (setq data_list_ (list 
                          (x_sym (car data_list_) x_num_)
                          (y_sym (cadr data_list_) y_num_)
                        )
        )
      )
    )
  )
;
;CLEANER_FUNC Ta Trai
  (defun TA:get_name_block_in_drawing_to_list ()
    ;get_obj_file_
      (setq multi_blocks_obj (vla-get-blocks (vla-get-ActiveDocument (vlax-get-acad-object))))
      (setq block_list_ ())
    ;
    ;method_for_get_name_block_in_drawing
      ;method_1_get_name_
        (vlax-for block_ multi_blocks_obj 
          (setq block_list_ (append block_list_ (list (vla-get-name block_))))
        )
      ;
      ; ;method_2_get_name_
      ;   (setq block_i 0)
      ;   (while (< block_i (vla-get-count multi_blocks_obj))
      ;     (setq block_ (vla-item multi_blocks_obj block_i))
      ;     (setq block_list_ (append block_list_ (list (vla-get-name block_))))
      ;     (setq block_i (1+ block_i))
      ;   )
      ; ;
    ;
    ;sorting_name_block
      (setq sorted_block_list_ (acad_strlsort block_list_))
    ;
    ;preloop_and_while filtter_
      (setq sorted_block_list_i 0)
      (setq filter_sorted_block_ ())

      (while (< sorted_block_list_i (length sorted_block_list_))
        (setq filter_sorted_block_effectivename_ (nth sorted_block_list_i sorted_block_list_))
        
        (if (/= (substr filter_sorted_block_effectivename_ 1 1) "*") ; ตรวจสอบว่าชื่อเริ่มต้นด้วย *
          (progn
            (setq filter_sorted_block_ (cons filter_sorted_block_effectivename_ filter_sorted_block_))
          )
        )
        (setq sorted_block_list_i (+ sorted_block_list_i 1))
      )
    ;
    ;summary_total_block
      (setq filter_sorted_block_total (length filter_sorted_block_))
      (princ "\n                  |=====================|")
      (princ "\n                  | TOTAL BLOCK IN FILE |")
      (princ (strcat "\n                  |     = " (itoa filter_sorted_block_total) " block         |"))
      (princ "\n                  |          set        |")
      (princ "\n                  |---------------------|")
      (setq filter_sorted_block_ (acad_strlsort filter_sorted_block_))
    ;
  )
  (defun TA:RE_COLOR_ALL_NORMAL_OBJECT_CHANGE_ (c-main-color)
    (setq all_obj_in_block (ssget "x" 
                                  (list 
                                    ; (cons 0 "insert")       ;type of object
                                    ; (cons 8 "000 - GRID")   ;kind of layer
                                    ; (cons 2 "SSSS")       ;kind of nameblock
                                    ; (cons 62 1)           ;kind of color call sign with color code index
                                  )
                            )
    )
    (command "chprop" all_obj_in_block "" "c" c-main-color "")
  )
  (defun TA:RE_COLOR_ALL_DIM+LEADER_OBJ (dim-main-color)
    ;dim_obj_mode
      ; (setq ss (vlax-get-property (vlax-ename->vla-object (car (entsel))) 'objectname)) ;logic for testing
      ; (setq ss (vlax-dump-object (vlax-ename->vla-object (car (entsel))) 'objectname))  ;logic for testing
      ;user_input_ selection_dim_object
        (setq all_dim_out_block (ssget "x" 
                                        (list 
                                          (cons 0 "dimension")       ;type of object
                                          ; (cons 8 "000 - GRID")   ;kind of layer
                                          ; (cons 2 "SSSS")       ;kind of nameblock
                                          ; (cons 62 1)           ;kind of color call sign with color code index
                                        )
                                )
        )
      ;
      ; (command "pselect" all_dim_out_block "")
      (if (/= all_dim_out_block nil)
        (progn
          (setq all_dim_out_block_total (sslength all_dim_out_block))
          (setq all_dim_out_block_iii 0)
          (while
            (< all_dim_out_block_iii all_dim_out_block_total)
            (setq all_dim_out_block_ename (ssname all_dim_out_block all_dim_out_block_iii))
            (setq all_dim_out_block_obj (vlax-ename->vla-object all_dim_out_block_ename))
            ; (vlax-dump-object all_dim_out_block_obj)
              (cond 
                ((and 
                    (= (vlax-get-property all_dim_out_block_obj 'objectname) 
                        "AcDbAlignedDimension"
                    )
                  )
                  (progn 
                    (vla-put-textcolor all_dim_out_block_obj dim-main-color)
                    (vla-put-dimensionlinecolor all_dim_out_block_obj dim-main-color)
                    (vla-put-extensionlinecolor all_dim_out_block_obj dim-main-color)
                  )
                  (princ "\n")
                )
                ((and 
                    (= (vlax-get-property all_dim_out_block_obj 'objectname) 
                        "AcDb2LineAngularDimension"
                    )
                  )
                  (progn 
                    (vla-put-textcolor all_dim_out_block_obj dim-main-color)
                    (vla-put-dimensionlinecolor all_dim_out_block_obj dim-main-color)
                    (vla-put-extensionlinecolor all_dim_out_block_obj dim-main-color)
                  )
                )
                ((and 
                    (= (vlax-get-property all_dim_out_block_obj 'objectname) 
                        "AcDbRotatedDimension"
                    )
                  )
                  (progn 
                    (vla-put-textcolor all_dim_out_block_obj dim-main-color)
                    (vla-put-dimensionlinecolor all_dim_out_block_obj dim-main-color)
                    (vla-put-extensionlinecolor all_dim_out_block_obj dim-main-color)
                  )
                )
                ((and 
                    (= (vlax-get-property all_dim_out_block_obj 'objectname) 
                        "AcDbArcDimension"
                    )
                  )
                  (progn 
                    (vla-put-textcolor all_dim_out_block_obj dim-main-color)
                    (vla-put-dimensionlinecolor all_dim_out_block_obj dim-main-color)
                    (vla-put-extensionlinecolor all_dim_out_block_obj dim-main-color)
                  )
                )
                ((and 
                    (= (vlax-get-property all_dim_out_block_obj 'objectname) 
                        "AcDbDiametricDimension" 
                    )
                  )
                  (progn 
                    (vla-put-textcolor all_dim_out_block_obj dim-main-color)
                    (vla-put-dimensionlinecolor all_dim_out_block_obj dim-main-color)
                  )
                )
                ((and 
                    (= (vlax-get-property all_dim_out_block_obj 'objectname) 
                        "AcDbOrdinateDimension" 
                    )
                  )
                  (progn 
                    (vla-put-textcolor all_dim_out_block_obj dim-main-color)
                    (vla-put-ExtensionLineColor  all_dim_out_block_obj dim-main-color)
                  )
                )
                ((and 
                    (= (vlax-get-property all_dim_out_block_obj 'objectname) 
                        "AcDbRadialDimension" 
                    )
                  )
                  (progn 
                    (vla-put-textcolor all_dim_out_block_obj dim-main-color)
                    (vla-put-dimensionlinecolor all_dim_out_block_obj dim-main-color)
                  )
                )
              )
            ; (vla-put-textcolor all_dim_out_block_obj dim-main-color)
            ; (vla-put-dimensionlinecolor all_dim_out_block_obj dim-main-color)
            ; ; (vla-put-extensionlinecolor all_dim_out_block_obj dim-main-color)
            (setq all_dim_out_block_iii (+ all_dim_out_block_iii 1))
          )
        )
        (princ "\n")
      )
    ;
    ;leader_obj_mode
      ;user_input_ selection_leader_object    
        (setq all_leader_out_block (ssget "x" 
                                      (list 
                                        (cons 0 "leader")       ;type of object
                                        ; (cons 8 "000 - GRID")   ;kind of layer
                                        ; (cons 2 "SSSS")       ;kind of nameblock
                                        ; (cons 62 1)           ;kind of color call sign with color code index
                                      )
                              )
        )
      ;
        (if (/= all_leader_out_block nil)
          (progn
            (setq all_leader_out_block_total (sslength all_leader_out_block))
            (setq all_leader_out_block_iii 0)
            (while
              (< all_leader_out_block_iii all_leader_out_block_total)
              (setq all_leader_out_block_ename (ssname all_leader_out_block all_leader_out_block_iii))
              (setq all_leader_out_block_obj (vlax-ename->vla-object all_leader_out_block_ename))
              (vla-put-dimensionlinecolor all_leader_out_block_obj dim-main-color)
              (setq all_leader_out_block_iii (+ all_leader_out_block_iii 1))
            )
          )
          (princ "\n")
        )
    ;
  )
;
;delete_func_
  (defun TA:delete_block_ (selection_set_ efname_val_1 efname_val_2 efname_val_3)
    ;for testing_data_
      ; (setq selection_set_ (ssget ))
      ; (setq efname_val_ "special_block2460499.7018" )
    ;
    ;get_data_
      
    ;
    ;prelooop_and_while
      (setq selection_set_i 0)
      (while  (< selection_set_i (sslength selection_set_))
        (setq selection_set_ename_ (ssname selection_set_ selection_set_i))
        (setq selection_set_ename_obj (vlax-ename->vla-object selection_set_ename_))
        
          ;delete_block_process
            (if
              (and 
                (/= (LM:effectivename selection_set_ename_obj) efname_val_1)
                (/= (LM:effectivename selection_set_ename_obj) efname_val_2)
                (/= (LM:effectivename selection_set_ename_obj) efname_val_3)
              )
              (progn
                (vla-delete selection_set_ename_obj)
              )
              (princ "/nnext")
            )
          ;
        
        (setq selection_set_i (+ selection_set_i 1))
      )
    ;

  )
;
;CREATE_OBJECT_FUNC
  ;text
    (defun create-text-vla (pt textString height rotation / acadDoc textObj) 
      (setq acadObj (vlax-get-acad-object))
      (setq doc (vla-get-ActiveDocument acadObj))
      (setq modelSpace (vla-get-ModelSpace doc))
      (setq textObj (vla-addtext modelSpace textString pt height))
      (vla-put-Height textObj height)
      (vla-put-Rotation textObj rotation)
      textObj
    )
  ;
  ;add+pline_data
    (defun TA:vla-AddLightWeightPolyline_(point_list_)
        ;; This example creates a lightweight polyline in model space.
        (setq acadObj (vlax-get-acad-object))
        (setq doc (vla-get-ActiveDocument acadObj))
        
        ;; Define the intersection points
        

        ;; Convert 3D points to a flat 2D list
        (setq points (apply 'append (mapcar '(lambda (pt) (list (car pt) (cadr pt))) point_list_)))

        ;; Convert to safe array
        (setq pointArray (vlax-make-safearray vlax-vbDouble (cons 0 (- (length points) 1))))
        (vlax-safearray-fill pointArray points)
            
        ;; Create a lightweight Polyline object in model space
        (setq modelSpace (vla-get-ModelSpace doc))
        (setq plineObj (vla-AddLightWeightPolyline modelSpace pointArray))
        (vla-ZoomAll acadObj)
    )
    (defun create-pline (coords)
      (if (= (length coords) 0)
          nil
        (progn
          ; สร้างพอลีไนจากค่าพิกัด
          (command "pline" (car coords) )
          
          ; วนลูปผ่านพิกัดทั้งหมดและเชื่อมต่อเส้นต่อเนื่อง
          (foreach coord (cdr coords)
            (command coord )
          )
        )
      )
      (command "")
    )
    (defun create-plines (coords close_loop_)
      (if (= (length coords) 0)
          nil
        (progn
          ; สร้างพอลีไนจากค่าพิกัด
          (command "pline" (car coords) )
          
          ; วนลูปผ่านพิกัดทั้งหมดและเชื่อมต่อเส้นต่อเนื่อง
          (foreach coord (cdr coords)
            (command coord )
          )
        )
      )
      (command "")
      (cond
        ( (= close_loop_ "close") 
          (progn 
            (setq new_line_data_ (vlax-ename->vla-object (entlast)))
            (vla-put-closed new_line_data_ :vlax-true)
          )
        )
        ((= close_loop_ "open") 
          (progn 
            (setq new_line_data_ (vlax-ename->vla-object (entlast)))
            (vla-put-closed new_line_data_ :vlax-false)
          )
        )
      )
    )
    (defun TA:vla-addvertex_ (pline_obj_ vertex_num_ point_list_)
      (setq point_list_new (remove_single_list_ 2 point_list_))
      (setq newVertex (vlax-make-safearray vlax-vbDouble '(0 . 1)))
      (vlax-safearray-fill newVertex point_list_new)
      (vla-addvertex pline_obj_ vertex_num_ newVertex)
    )
    (defun TA:add_vertex_point_pline_via_breakpt_ (ename_cut_edge_ ename_intersection_obj_)
      
      ;get_data_main_cut_and_main_intersection_
        (setq bb_obj_ (vlax-ename->vla-object ename_cut_edge_))     
        (setq ss_obj_ (vlax-ename->vla-object ename_intersection_obj_))     
        (setq intersec_ (LM:intersections+0 
                          bb_obj_
                          ss_obj_
                          acextendnone
                        )
        )
        (setq vertex_list_ (TA:Get_Pline_vertext_angle_case1 
                              ename_intersection_obj_
                            )
        )
        (setq intersec_i 0)
      ;
      ;preloop_and_while adding_vertex_point_
        (setq ename_list_ ())
        (setq ssadd_list_ (ssadd))
        (while   (< intersec_i (length intersec_))
          (setq intersec_val_ (nth intersec_i intersec_))
          (command "breakatpoint" ename_intersection_obj_ intersec_val_ "")
          (setq new_E_ (entlast))
          ; (command "pselect" new_E_)
          ; (command "pselect" ss)
          (setq ename_list_ (cons new_E_ ename_list_))
          (setq ssadd_list_ (ssadd new_E_ ssadd_list_))
          (setq ssadd_list_ (ssadd ename_intersection_obj_ ssadd_list_))
          (sslength ssadd_list_)
          (command "_.pedit" "_m" ssadd_list_ "" "_j" "" "")
          (setq ename_intersection_obj_ (entlast))
          (setq intersec_i (+ intersec_i 1))
          
        )
      ;
    )
    (defun TA:add_vertex_point_pline_via_breakpt_1 (ename_cut_edge_ ename_intersection_obj_)
      
          
          ;get_data_main_cut_and_main_intersection_
            (setq bb_obj_ (vlax-ename->vla-object ename_cut_edge_))     
            (setq ss_obj_ (vlax-ename->vla-object ename_intersection_obj_))     
            (setq intersec_ (LM:intersections+0 
                              bb_obj_
                              ss_obj_
                              acextendnone
                            )
            )
            (command "pedit" ename_intersection_obj_ "" "c" "" )
            (setq vertex_list_ (TA:Get_line_ins_point_ 
                                  ename_intersection_obj_
                                )
            )
            (setq intersec_i 0)
          ;
          ;preloop_and_while adding_vertex_point_
            (setq ename_list_ ())   
            (setq ssadd_list_ (ssadd))
            (while   (< intersec_i (length intersec_))
              (setq intersec_val_ (nth intersec_i intersec_))
              (command "breakatpoint" ename_intersection_obj_ intersec_val_ "")
              
              (setq new_E_ (entlast))
              ; (command "pselect" new_E_)
              ; (command "pselect" ss)
              (setq ename_list_ (cons new_E_ ename_list_))
              (setq ssadd_list_ (ssadd new_E_ ssadd_list_))
              (setq ssadd_list_ (ssadd ename_intersection_obj_ ssadd_list_))
              (sslength ssadd_list_)
              (command "_.pedit" "_m" ssadd_list_ "y" "" "_j" "" "")
              (command "_.pedit" "_m" ssadd_list_ "" "y" )
              (setq ename_intersection_obj_ (entlast))
              (setq intersec_i (+ intersec_i 1))
              
            )
          ;
    )
  ;
  ;add_circle
    (defun TA:vla-addarc_ (center_ rad_ point_list_ )
      ; point_list_ must be two coord set in list
      ; do not vlax-3d_point w/ agument
      ;sub_func_
        (defun CO:sort_by_val_ (val_ list_ )  ;เรียงชุดข้อมูลตามแนวแกน
          (if (< val_ (length (car list_)))
            (progn
              (setq sortedLst (vl-sort list_ (function (lambda (a b) (< (nth val_ a) (nth val_ b))))))
            )
            (setq error_ "The number of val is less than list")
          )
        )
      ;
      ;basic_get_data_
        (setq acadObj (vlax-get-acad-object))
        (setq doc (vla-get-ActiveDocument acadObj))
        (setq modelSpace (vla-get-ModelSpace doc))
      ;
      ;advance_get_data
        (setq point_list_ (reverse (append (CO:sort_by_val_ 1 point_list_) (list (car point_list_)))))
      ;
      ;preloop_and_while sorting arc_line
        (setq angle_list_ ())
        (setq point_list_i 0)
        (setq point_list_ii 1)
        (while (< point_list_i (- (length point_list_) 1))
          (setq point_list_set_1 (nth point_list_i point_list_))
          (setq angle_ (atof (angtos (angle center_ point_list_set_1))))
          (setq sum (list
                      point_list_set_1
                      angle_
                    )
          )
          (setq angle_list_ (cons sum angle_list_))
          (setq point_list_i (+ point_list_i 1))
          (setq point_list_ii (+ point_list_ii 1))
        )
      ;
      (setq point_list_ (append (CO:sort_by_val_ 1 angle_list_) (list (car (CO:sort_by_val_ 1 angle_list_) ))) )
      (setq point_list_i 0)
      (setq point_list_ii 1)
      (while (< point_list_i (- (length point_list_) 1))
        (setq point_list_set_1 (car (nth point_list_i point_list_)))
        (setq point_list_set_2 (car (nth point_list_ii point_list_)))
        (setq start_ang_ (angle center_ point_list_set_1))
        (setq end_ang_ (angle center_ point_list_set_2))
        ; (setq rad_ (distance center_ point_list_set_1))
        
        (vla-addarc modelSpace (vlax-3d-point center_) rad_  start_ang_ end_ang_)
        (setq point_list_i (+ point_list_i 1))
        (setq point_list_ii (+ point_list_ii 1))
      )
      
    )
  ;
  ;add-point
    (defun vla-addpoint_ (point) 
      (setq acadObj (vlax-get-acad-object))
      (setq doc (vla-get-ActiveDocument acadObj))
      (setq modelSpace (vla-get-ModelSpace doc))
      (vla-addpoint modelSpace (vlax-3d-point point))
    )
  ;
  ;get_line
    (defun TA:Get_line_ins_point_ (ename_)
      
      ; (setq ename_ (car (entsel)))
      (setq ename_obj_ (vlax-ename->vla-object ename_))
      (setq ename_obj_str_pt_ (vlax-safearray->list (vlax-variant-value (vla-get-startpoint ename_obj_))))
      (setq ename_obj_end_pt_ (vlax-safearray->list (vlax-variant-value (vla-get-endpoint ename_obj_))))
      (setq sum_ (list
                   ename_obj_str_pt_
                   ename_obj_end_pt_
                 )
      )
    )
    
  ;
  ;offset
    (defun TA:Offset_line (ename num_ )
      ; (setq 1-PL_en_ (car (entsel)))
      (setq 1-PL_en_obj (vlax-ename->vla-object ename))
      (vla-Offset 1-PL_en_obj num_)
    )
  ;
;
;block_editor_FUNC
  (defun TA:set-block-explodable (block-name allow-exploding)
    ;example_using
      ;;allow-exploding = :vlax-true or :vlax-false
      ; (set-block-explodable "A$C5b7816c3" :vlax-true)
      ; (set-block-explodable "A$C5b7816c3" :vlax-false)
    ;
    ;for testing code
      ; (setq block-name "001 - DYNAMIC LV" )
      ; (setq allow-exploding :vlax-false )
      ; (setq allow-exploding :vlax-true )
    ;
    (setq doc (vla-get-ActiveDocument (vlax-get-acad-object)))
    (setq block-def (vla-Item (vla-get-Blocks doc) block-name))
    (vla-get-Explodable block-def )
    (if (/= block-def nil)  
      (progn
        (vla-put-Explodable block-def allow-exploding)
      )
      (princ (strcat "\nBlock " block-name " not found."))
    )
  )
  (defun TA:set-block-blockscaling (block-name parameter)
  ;example_using
    ;;parameter = acAny or acUniform
    ; (set-block-explodable "A$C5b7816c3" acAny)
    ; (set-block-explodable "A$C5b7816c3" acUniform)
  ;
  (setq doc (vla-get-ActiveDocument (vlax-get-acad-object)))
  (setq block-def (vla-Item (vla-get-Blocks doc) block-name))
  (if block-def
    (vla-put-blockscaling block-def parameter)
    (princ (strcat "\nBlock " block-name " not found."))
  )
  )
  (defun c:DYN_ADD_VISIBILITY_advs_ ()
    (setq input_ins_ (getpoint ))
    (setq name_vis_ "view")
    (command "BPARAMETER" "v" "L" name_vis_ input_ins_ 1)
    (command "-Bvstate" "s" "VisibilityState0")
    ;preloop_and_while_
      (setq visibility_list_ (list
                              "1"
                              "2"
                              "3"
                              "4"
                              "5"
                            )
      )
      (setq visibility_list_i 0)

      (while (< visibility_list_i (length visibility_list_))
        (setq visibility_list_SEQ (nth visibility_list_i visibility_list_))
        (command "-Bvstate" "n" visibility_list_SEQ "c" )
        (setq visibility_list_i (+ visibility_list_i 1))
      )
    ;
    ;setting first visibility_list
      ;-
    ;
  )
;
;test_command
  (defun C:Dumpit ( / ent) 
    (while (setq ent (entsel)) 
      (vlax-Dump-Object 
        (vlax-Ename->Vla-Object (car ent)) 
      ) 
    ) 
    (princ) 
  )
  (defun c:t1_ins_vla-getboundingbox ()
    (setq ss (vlax-ename->vla-object (car (entsel))) )
    (vla-getboundingbox ss 'ins_min 'ins_max)
                (setq ins_min (vlax-safearray->list ins_min))
                (setq ins_max (vlax-safearray->list ins_max))

    (command "point" ins_min)
    (command "point" ins_max)
  )
  (defun c:t2_find_objname ()
    (setq obj_name_ (vla-get-objectname (vlax-ename->vla-object (car (entsel)))))
  )
;
;Common_commmand 
  (defun c:ROUND_INSERTIONPOINT_reins_ ()
    ;selection_set
      (if  ;pre_select_ssget_or_post_select_ssget
        (= 
          (setq ss_pre_filter_set_xx (ssget "I" 
                                            (list 
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn 
          (setq ss_pre_filter_set_xx (ssget 
                                        (list 
                                          (cons 0 "INSERT") ;type of object
                                          ; (cons 8 "000 - GRID")   ;kind of layer
                                          ; (cons 2 "000-GRIDLINE_DYN")       ;kind of nameblock
                                          ; (cons 62 1)           ;kind of color call sign with color code index
                                        )
                                      )
          )
        )
        (sslength ss_pre_filter_set_xx)
      )
    ;
    ;get_efname_
      (setq blk_name_ (LM:effectivename (vlax-ename->vla-object (car (entsel)))))
    ;
    ;ssget_filtter
      (setq ss_prop_filter_ (TA:Prop_Filter_ss_set_ ss_pre_filter_set_xx "effectivename" blk_name_))
    ;
    ;preloop_and_while_rework_inspoint
      (setq ss_prop_filter_i 0)
      (while  (< ss_prop_filter_i (sslength ss_prop_filter_))
        (setq ss_prop_filter_ename_ (ssname ss_prop_filter_ ss_prop_filter_i))
        (setq ss_prop_filter_obj_ (vlax-ename->vla-object ss_prop_filter_ename_))
        (setq ss_prop_filter_obj_ins_ (TA:ename+vla-get-insertionpoint ss_prop_filter_obj_))
        
        ;re_location_inspt_
          ;get_data
            (setq new_input_ins_ (list
                                      (setq ss_prop_filter_obj_ins_x (LM:round (car (nth 1 ss_prop_filter_obj_ins_))))
                                      (setq ss_prop_filter_obj_ins_y (LM:round (cadr (nth 1 ss_prop_filter_obj_ins_))))
                                      (setq ss_prop_filter_obj_ins_z (LM:round (caddr (nth 1 ss_prop_filter_obj_ins_))))                             
                                    )
            )
          ;
          (vla-put-insertionpoint ss_prop_filter_obj_ (vlax-3d-point new_input_ins_))
        ;
        (setq ss_prop_filter_i (+ ss_prop_filter_i 1))
      )
    ;
  )
  (defun c:BOL ()
    ;get_osmode_process
      (setq getold_osmode_ (getvar "osmode"))
      (setq zero_osmode_ (setvar "osmode" 0))
    ;
    ;user_input
      (setq ref_pline_or_block_ (car (entsel "specify PLINE OR BLOCK OBJECT" )))
    ;
    ;MAIN_IDEA_COMMAND_
      (setq lower_upper_inspoint_ (TA:Find_boundary_line_ ref_pline_or_block_))
      (command "rectangle" (car lower_upper_inspoint_) (cadr lower_upper_inspoint_))
    ;  
    ;Change_Color_process
      (setq new_obj_ (vlax-ename->vla-object (entlast)))
      (setq new_obj_input_color_ (vla-put-color new_obj_ 250))
    ;
    ;return_osmode_process_
      (setq return_osmode_ (setvar "osmode" getold_osmode_))
    ;
  )
  (defun c:Multi_wipeout_mlwe ()
    ;selection_set
      (if  ;pre_select_ssget_or_post_select_ssget
        (= 
          (setq ss_pre_filter_set_xx_ (ssget "I" 
                                            (list 
                                              (cons 0 "lwpolyline") ;type of object
                                              ; (cons 8 "000 - GRID")   ;kind of layer
                                              ; (cons 2 "000-GRID_LINE_DYN")       ;kind of nameblock
                                              ; (cons 62 1)           ;kind of color call sign with color code index
                                            )
                                      )
          )
          nil
        )
        (progn 
          (setq ss_pre_filter_set_xx_ (ssget 
                                        (list 
                                          (cons 0 "lwpolyline") ;type of object
                                          ; (cons 8 "000 - GRID")   ;kind of layer
                                          ; (cons 2 "000-GRIDLINE_DYN")       ;kind of nameblock
                                          ; (cons 62 1)           ;kind of color call sign with color code index
                                        )
                                      )
          )
        )
        (sslength ss_pre_filter_set_xx_)
      )
    ;
    ;preloop_and_while
    (setq ss_pre_filter_set_xx_i 0)
    (while (< ss_pre_filter_set_xx_i (sslength ss_pre_filter_set_xx_))
      (setq ss_pre_filter_set_xx_ename_ (ssname ss_pre_filter_set_xx_ ss_pre_filter_set_xx_i))
      (setq ss_pre_filter_set_xx_obj_ (vlax-ename->vla-object ss_pre_filter_set_xx_ename_))
      (setq ss_pre_filter_set_xx_ename_close_line (vla-put-closed ss_pre_filter_set_xx_obj_ :vlax-true))
      
        (command "wipeout" "p"  ss_pre_filter_set_xx_ename_ "n" )
        (setq wipeput_ename_ (entlast))
        (setq wipeput_ename_obj_ (vlax-ename->vla-object wipeput_ename_))
        (vla-put-layer wipeput_ename_obj_ "000 - WIPEOUT")
        (vla-put-color wipeput_ename_obj_ 256)
        (command "_draworder" wipeput_ename_ "" "b" )
        
    
      (setq ss_pre_filter_set_xx_i (+ ss_pre_filter_set_xx_i 1))
    )
    ;
    
    
    
    
    
    
    
  )
  (defun c:make_detail_box_mkbx_ ()
    ;get_point_data_
      (setq get_pt_ (getpoint ))
      ; (setvar "orthomode" 1)
    ;
    ;get_honrizontal_data_
      (setq dist_hon (getdist get_pt_ ) )
      (setq hon_pt_ (polar get_pt_ 0.0 dist_hon))
      (setq hon_pt_- (polar get_pt_ (deg-to-rad 180.00) dist_hon))
    ;
    ;get_vertical_data_
      (setq dist_ver (getdist get_pt_ ) )
      (setq ver_pt_ (polar get_pt_ (deg-to-rad 90.00) dist_ver))
      (setq ver_pt_- (polar get_pt_ (deg-to-rad 270.00) dist_ver))
    ;
    ;sorting_max_legth_
      (setq length_list_rec (list
                              dist_hon
                              dist_ver
                            )
      )
      (setq min-length (car (vl-sort  length_list_rec '<)))
    ;
    ;get_conner_
      (setq top_conner_ (list
                          (car hon_pt_)
                          (cadr ver_pt_)
                        )
      )
      (setq bot_conner_ (list
                          (car hon_pt_-)
                          (cadr ver_pt_-)
                        )
      )
    ;
  
    ;use_input_for_specify_fllet_rec_
      (setq fllet_rec_val "not pass" )
      (while (= fllet_rec_val "not pass")
        
        (setq fllet_rec_ (cond ( (getint (strcat "\nspecify fllet_rec_<" (rtos (setq fllet_rec_ (cond (fllet_rec_) (1.0) ) ) ) "> : " ) ) ) (fllet_rec_) ) )
        (if
          (< (LM:round (* min-length 0.9)) fllet_rec_)
          (progn
            (setq fllet_rec_val "not pass" )
            (alert "fllet rectangle more than min-length ractangle ")
          )
          (setq fllet_rec_val "pass" )
        )
      )
    ;
    ; ;make_new_object_
    ;   (command "point" get_pt_)
    ;   (command "point" top_conner_)
    ;   (command "point" bot_conner_)
      (command "rectangle" bot_conner_ top_conner_  )
      (command "fillet" "p" "r" fllet_rec_ "L" )
    ;
    ;put_prop_data_
      (setq entlast_ename_ (entlast))
      (vla-get-linetype (setq entlast_obj_ (vlax-ename->vla-object entlast_ename_)))
      (vla-put-linetype (setq entlast_obj_ (vlax-ename->vla-object entlast_ename_)) "byblock")
    ;

    
  )
  (defun c:save_dynamic_scale_scdyn_ ()
    ;user_input_
      (setq get_dynblock_ename_ (car (entsel "specify Object")))
      (setq dynamic_scale_ (cond ( (getreal (strcat "\nspecify_rotation_grid_line<" (rtos (setq dynamic_scale_ (cond (dynamic_scale_) (1.0) ) ) ) "> : " ) ) ) (dynamic_scale_) ) )
    ;
  
    (if (and ;condition rule
          ; (/= get_effectivename_ nil)
          (= (vla-get-isdynamicblock (vlax-ename->vla-object get_dynblock_ename_)) :vlax-true)
          ; (/= (vla-get-isdynamicblock (vlax-ename->vla-object get_effectivename_)) :vlax-true)
        )
      (progn ;add data
        ; (alert "\nplease select block object")
        ; (setq get_effectivename_ nil)
        ; (setq get_effectivename_obj_val_ nil)
        (setq get_effectivename_obj_val_ (LM:Effectivename (vlax-ename->vla-object get_dynblock_ename_)))
        (setq REF_get_att_list_ (LM:getdynprops (vlax-ename->vla-object get_dynblock_ename_)))
        (setq REF_get_att_list_total (length REF_get_att_list_))
        ;add more
      )
      (setq get_effectivename_ nil)
    )
    ;rescale_
      (setq basescale_ (vlax-3d-point dynamic_scale_ dynamic_scale_ dynamic_scale_))
      (vla-put-xscalefactor (vlax-ename->vla-object get_dynblock_ename_) dynamic_scale_ )
    ;
    ;preloop_and_while
      (setq REF_get_att_list_i 0)
      (while (< REF_get_att_list_i (length REF_get_att_list_))
        ;get_dynamic_data
          (setq REF_get_att_list_dynamicset_ (nth  REF_get_att_list_i REF_get_att_list_))
          (setq REF_get_att_list_dynamicset_name_ (nth 0 REF_get_att_list_dynamicset_) )
          (setq REF_get_att_list_dynamicset_val_ (cdr REF_get_att_list_dynamicset_))
        ;
        ;get_vis_data_
          (setq vis_name_ (LM:getvisibilityparametername (vlax-ename->vla-object get_dynblock_ename_) ))
          (setq vis_stage_ (LM:getvisibilitystate (vlax-ename->vla-object get_dynblock_ename_) ))
          (LM:SetVisibilityState (vlax-ename->vla-object get_dynblock_ename_) vis_stage_ )
        ;
        ;get_filp_data_
          (setq Flip_data_ (LM:toggleflipstate (vlax-ename->vla-object get_dynblock_ename_)))
        ;
        
        
        (if (/= REF_get_att_list_dynamicset_name_ "Origin")
          (progn
            (LM:setdynpropvalue (vlax-ename->vla-object get_dynblock_ename_) REF_get_att_list_dynamicset_name_ REF_get_att_list_dynamicset_val_ )
          )
          (princ "next ")
        )
        
        (setq REF_get_att_list_i (+ REF_get_att_list_i 1))
      )
    ;
  )
  (defun c:STAMP_START_POINT_STP_ ()
    ;Stamp_ dynamic block "000SYM-START_POINT_" /w RECTANGLE_BLOCK
    (setq main_rec_ename_ (car (entsel "specify Object")))
    (setq rec_point_ (TA:find_center main_rec_ename_ ))
    (command "insert" "000SYM-START_POINT_" rec_point_ 0.1 0 )
  )
;




(defun c:R1R_PROJECT_TO_PROJECT ()
  (setq main (car (entsel "first pattern for copy")))
  (setq NAME_JOB_1 (LM:vl-getattributevalue (vlax-ename->vla-object main) "NAME_JOB_1"))
  (setq NAME_JOB_2 (LM:vl-getattributevalue (vlax-ename->vla-object main) "NAME_JOB_2"))
  (setq NAME_PROJECT_1 (LM:vl-getattributevalue (vlax-ename->vla-object main) "NAME_PROJECT_1"))
  (setq NAME_PROJECT_2 (LM:vl-getattributevalue (vlax-ename->vla-object main) "NAME_PROJECT_2"))
  (setq NAME_PROJECT_3 (LM:vl-getattributevalue (vlax-ename->vla-object main) "NAME_PROJECT_3"))
  (setq DRAWING_NO1 (LM:vl-getattributevalue (vlax-ename->vla-object main) "DRAWING_NO1"))
  (setq SUPERLINK (LM:vl-getattributevalue (vlax-ename->vla-object main) "SUPERLINK"))
  (setq NAMEFILE (LM:vl-getattributevalue (vlax-ename->vla-object main) "NAMEFILE"))
  
  ; (setq DRAWING_NO2 (LM:vl-getattributevalue (vlax-ename->vla-object main) "DRAWING_NO2"))
  
  
  
  
  (setq mySet (ssget (list 
                      ;  (cons 8 "0") 
                       (cons 0 "INSERT") 
                      ;  (cons 2 "d2d")
                     ) 
              ) 
  )
  (setq entityCount (sslength mySet))
  
  (setq i 0)
  (while (< i entityCount) ; เมื่อลำดับยังไม่ถึง entityCount
      (setq ejc (ssname mySet i)) ; ดึง entity ที่ลำดับ i จาก mySet
      (setq o (vlax-ename->vla-object ejc))

      ; (setq entity1 (ssname mySet 1)) 
      ; (setq entity2 (ssname mySet 2))
      ; (setq entity3 (ssname mySet 0)) 
      ; (setq entity4 (ssname mySet 3)) 

      (setq o (vlax-ename->vla-object ejc))
      (LM:vl-setattributevalue o "NAME_JOB_1" NAME_JOB_1)
      (LM:vl-setattributevalue o "NAME_JOB_2" NAME_JOB_2)
  
      (LM:vl-setattributevalue o "NAME_PROJECT_1" NAME_PROJECT_1)
      (LM:vl-setattributevalue o "NAME_PROJECT_2" NAME_PROJECT_2)
      (LM:vl-setattributevalue o "NAME_PROJECT_3" NAME_PROJECT_3)
    
      (LM:vl-setattributevalue o "DRAWING_NO1" DRAWING_NO1)
    

    
      (LM:vl-setattributevalue o "SUPERLINK" SUPERLINK)
      (LM:vl-setattributevalue o "NAMEFILE" NAMEFILE)
     
      ; (setq M_D (strcat "M10" (itoa (1+ i))))
      ; (LM:vl-setattributevalue o "FAC" M_D)
  
      ; เพิ่มลำดับ
      (setq i (1+ i))
  )
)
(defun c:R2R_PART_TO_PROJECT ()
  (setq main (car (entsel)))
    (setq CODE_VALUE (LM:vl-getattributevalue (vlax-ename->vla-object main) "CODE_VALUE"))
  
      (setq PART_NAME_VALUE_1 (LM:vl-getattributevalue (vlax-ename->vla-object main) "PART_NAME_VALUE_1"))
      (setq PART_NAME_VALUE_2 (LM:vl-getattributevalue (vlax-ename->vla-object main) "PART_NAME_VALUE_2"))
      (setq PART_NAME_VALUE_3 (LM:vl-getattributevalue (vlax-ename->vla-object main) "PART_NAME_VALUE_3"))
  
  
      (setq MATTERIAL_VALUE (LM:vl-getattributevalue (vlax-ename->vla-object main) "MATTERIAL_VALUE"))
      (setq SPEC_VALUE (LM:vl-getattributevalue (vlax-ename->vla-object main) "SPEC_VALUE"))
      (setq THICKNESS_VALUE (LM:vl-getattributevalue (vlax-ename->vla-object main) "THICKNESS_VALUE"))
  
      (setq COATING_VALUE1 (LM:vl-getattributevalue (vlax-ename->vla-object main) "COATING_VALUE"))
      (setq COATING_VALUE2(LM:vl-getattributevalue (vlax-ename->vla-object main) "COATING_VALUE2"))
  

  
  
  ; (setq DRAWING_NO2 (LM:vl-getattributevalue (vlax-ename->vla-object main) "DRAWING_NO2"))
  
  
  
  
  (setq mySet (ssget (list 
                      ;  (cons 8 "0") 
                       (cons 0 "INSERT") 
                      ;  (cons 2 "d2d")
                     ) 
              ) 
  )
  (setq entityCount (sslength mySet))
  
  (setq i 0)
  (while (< i entityCount) ; เมื่อลำดับยังไม่ถึง entityCount
      (setq ejc (ssname mySet i)) ; ดึง entity ที่ลำดับ i จาก mySet
      (setq o (vlax-ename->vla-object ejc))

      ; (setq entity1 (ssname mySet 1)) 
      ; (setq entity2 (ssname mySet 2))
      ; (setq entity3 (ssname mySet 0)) 
      ; (setq entity4 (ssname mySet 3)) 

      (setq o (vlax-ename->vla-object ejc))
      (LM:vl-setattributevalue o "NAME_PART_CODE1" CODE_VALUE)
      
  
      (LM:vl-setattributevalue o "NAME_PART_NAME1" PART_NAME_VALUE_1)
      (LM:vl-setattributevalue o "NAME_PART_NAME2" PART_NAME_VALUE_2)
      (LM:vl-setattributevalue o "NAME_PART_NAME3" PART_NAME_VALUE_3)
    
      (LM:vl-setattributevalue o "NAME_MAT" MATTERIAL_VALUE)
      (LM:vl-setattributevalue o "NAME_SPEC" SPEC_VALUE)
      (LM:vl-setattributevalue o "NAME_THK" THICKNESS_VALUE)

      (LM:vl-setattributevalue o "NAME_FINISH1" COATING_VALUE1)
      (LM:vl-setattributevalue o "NAME_FINISH2" COATING_VALUE2)
    
      (LM:vl-setattributevalue o "NAME_TITLE_1" PART_NAME_VALUE_1)
      (LM:vl-setattributevalue o "NAME_TITLE_2" PART_NAME_VALUE_2)
      (LM:vl-setattributevalue o "NAME_TITLE_3" PART_NAME_VALUE_3)
     
      ; (setq M_D (strcat "M10" (itoa (1+ i))))
      ; (LM:vl-setattributevalue o "FAC" M_D)
  
      ; เพิ่มลำดับ
      (setq i (1+ i))
  )
)
(defun c:R3R_PART_TO_PART ()
  (setq main (car (entsel)))
    (setq CODE_VALUE (LM:vl-getattributevalue (vlax-ename->vla-object main) "CODE_VALUE"))
  
      (setq PART_NAME_VALUE_1 (LM:vl-getattributevalue (vlax-ename->vla-object main) "PART_NAME_VALUE_1"))
      (setq PART_NAME_VALUE_2 (LM:vl-getattributevalue (vlax-ename->vla-object main) "PART_NAME_VALUE_2"))
  
      (setq MATTERIAL_VALUE (LM:vl-getattributevalue (vlax-ename->vla-object main) "MATTERIAL_VALUE"))
      (setq SPEC_VALUE (LM:vl-getattributevalue (vlax-ename->vla-object main) "SPEC_VALUE"))
      (setq BLANK_SIZE_VALUE (LM:vl-getattributevalue (vlax-ename->vla-object main) "BLANK_SIZE_VALUE"))
      (setq THICKNESS_VALUE (LM:vl-getattributevalue (vlax-ename->vla-object main) "THICKNESS_VALUE"))
      (setq COATING_VALUE (LM:vl-getattributevalue (vlax-ename->vla-object main) "COATING_VALUE"))
      (setq LENGTH_VALUE (LM:vl-getattributevalue (vlax-ename->vla-object main) "LENGTH_VALUE"))
      (setq LENGTH_VALUE_2 (LM:vl-getattributevalue (vlax-ename->vla-object main) "LENGTH_VALUE_2"))
    (setq TOTAL_VALUE (LM:vl-getattributevalue (vlax-ename->vla-object main) "TOTAL_VALUE"))
  ; (setq DRAWING_NO2 (LM:vl-getattributevalue (vlax-ename->vla-object main) "DRAWING_NO2"))
  
  
  
  
  (setq mySet (ssget (list 
                      ;  (cons 8 "0") 
                       (cons 0 "INSERT") 
                      ;  (cons 2 "d2d")
                     ) 
              ) 
  )
  (setq entityCount (sslength mySet))
  
  (setq i 0)
  (while (< i entityCount) ; เมื่อลำดับยังไม่ถึง entityCount
      (setq ejc (ssname mySet i)) ; ดึง entity ที่ลำดับ i จาก mySet
      (setq o (vlax-ename->vla-object ejc))

      ; (setq entity1 (ssname mySet 1)) 
      ; (setq entity2 (ssname mySet 2))
      ; (setq entity3 (ssname mySet 0)) 
      ; (setq entity4 (ssname mySet 3)) 

      (setq o (vlax-ename->vla-object ejc))
      (LM:vl-setattributevalue o "CODE_VALUE" CODE_VALUE)
      
  
      (LM:vl-setattributevalue o "PART_NAME_VALUE_1" PART_NAME_VALUE_1)
      (LM:vl-setattributevalue o "PART_NAME_VALUE_2" PART_NAME_VALUE_2)
    
      (LM:vl-setattributevalue o "MATTERIAL_VALUE" MATTERIAL_VALUE)
      (LM:vl-setattributevalue o "SPEC_VALUE" SPEC_VALUE)
      (LM:vl-setattributevalue o "BLANK_SIZE_VALUE" BLANK_SIZE_VALUE)
      (LM:vl-setattributevalue o "THICKNESS_VALUE" THICKNESS_VALUE)
      (LM:vl-setattributevalue o "COATING_VALUE" COATING_VALUE)
      (LM:vl-setattributevalue o "LENGTH_VALUE" LENGTH_VALUE)
      (LM:vl-setattributevalue o "LENGTH_VALUE_2" LENGTH_VALUE_2)

      (LM:vl-setattributevalue o "TOTAL_VALUE" TOTAL_VALUE)
     
      ; (setq M_D (strcat "M10" (itoa (1+ i))))
      ; (LM:vl-setattributevalue o "FAC" M_D)
  
      ; เพิ่มลำดับ
      (setq i (1+ i))
  )
)
(defun c:R4R_PROJECT_TO_PART ()
  (setq main (car (entsel)))
    (setq CODE_VALUE (LM:vl-getattributevalue (vlax-ename->vla-object main) "NAME_PART_CODE1"))
  
      (setq PART_NAME_VALUE_1 (LM:vl-getattributevalue (vlax-ename->vla-object main) "NAME_PART_NAME1"))
      (setq PART_NAME_VALUE_2 (LM:vl-getattributevalue (vlax-ename->vla-object main) "NAME_PART_NAME2"))
      (setq PART_NAME_VALUE_3 (LM:vl-getattributevalue (vlax-ename->vla-object main) "NAME_PART_NAME3"))
  
      (setq MATTERIAL_VALUE (LM:vl-getattributevalue (vlax-ename->vla-object main) "NAME_MAT"))
  
      (setq SPEC_VALUE (LM:vl-getattributevalue (vlax-ename->vla-object main) "NAME_SPEC"))

      (setq THICKNESS_VALUE (LM:vl-getattributevalue (vlax-ename->vla-object main) "NAME_THK"))
      (setq COATING_VALUE1 (LM:vl-getattributevalue (vlax-ename->vla-object main) "NAME_FINISH1"))
      (setq COATING_VALUE2 (LM:vl-getattributevalue (vlax-ename->vla-object main) "NAME_FINISH2"))
      (setq COATING_CONCAT (strcat COATING_VALUE1 "_" COATING_VALUE2))
  ; (setq TOTAL_VALUE (LM:vl-getattributevalue (vlax-ename->vla-object main) "TOTAL_VALUE"))
  ; (setq DRAWING_NO2 (LM:vl-getattributevalue (vlax-ename->vla-object main) "DRAWING_NO2"))
  ; (setq DRAWING_NO2 (LM:vl-getattributevalue (vlax-ename->vla-object main) "DRAWING_NO2"))
  
  
  
  
  (setq mySet (ssget (list 
                      ;  (cons 8 "0") 
                       (cons 0 "INSERT") 
                      ;  (cons 2 "d2d")
                     ) 
              ) 
  )
  (setq entityCount (sslength mySet))
  
  (setq i 0)
  (while (< i entityCount) ; เมื่อลำดับยังไม่ถึง entityCount
      (setq ejc (ssname mySet i)) ; ดึง entity ที่ลำดับ i จาก mySet
      (setq o (vlax-ename->vla-object ejc))

      ; (setq entity1 (ssname mySet 1)) 
      ; (setq entity2 (ssname mySet 2))
      ; (setq entity3 (ssname mySet 0)) 
      ; (setq entity4 (ssname mySet 3)) 

      (setq o (vlax-ename->vla-object ejc))
      (LM:vl-setattributevalue o "CODE_VALUE" CODE_VALUE)
      
  
      (LM:vl-setattributevalue o "PART_NAME_VALUE_1" PART_NAME_VALUE_1)
      (LM:vl-setattributevalue o "PART_NAME_VALUE_2" PART_NAME_VALUE_2)
      (LM:vl-setattributevalue o "PART_NAME_VALUE_3" PART_NAME_VALUE_3)
    
      (LM:vl-setattributevalue o "MATTERIAL_VALUE" MATTERIAL_VALUE)
      (LM:vl-setattributevalue o "SPEC_VALUE" SPEC_VALUE)
      
      (LM:vl-setattributevalue o "THICKNESS_VALUE" THICKNESS_VALUE)
      (LM:vl-setattributevalue o "COATING_VALUE1" COATING_VALUE1)
      (LM:vl-setattributevalue o "COATING_VALUE2" COATING_VALUE2)

     
      ; (setq M_D (strcat "M10" (itoa (1+ i))))
      ; (LM:vl-setattributevalue o "FAC" M_D)
  
      ; เพิ่มลำดับ
      (setq i (1+ i))
  )
)
(defun c:R5R_PART_PROJECT_TO_PRELIM_PROJECT ()
  ;specify_with_BU_NOOM_ONLY
  (setq main (car (entsel "first pattern for copy")))
  (setq NAME_PROJECT_1 (LM:vl-getattributevalue (vlax-ename->vla-object main) "NAME_PROJECT_1"))
  (setq NAME_PROJECT_2 (LM:vl-getattributevalue (vlax-ename->vla-object main) "NAME_PROJECT_2"))
  (setq NAME_PROJECT_3 (LM:vl-getattributevalue (vlax-ename->vla-object main) "NAME_PROJECT_3"))
  
  (setq NAME_TITLE_1 (LM:vl-getattributevalue (vlax-ename->vla-object main) "NAME_TITLE_1"))
  (setq NAME_TITLE_2 (LM:vl-getattributevalue (vlax-ename->vla-object main) "NAME_TITLE_2"))
  (setq NAME_TITLE_3 (LM:vl-getattributevalue (vlax-ename->vla-object main) "NAME_TITLE_3"))

  (setq DRAWING_NO2 (LM:vl-getattributevalue (vlax-ename->vla-object main) "DRAWING_NO2"))
  (setq TOTAL_SHEET_NO. (LM:vl-getattributevalue (vlax-ename->vla-object main) "TOTAL_SHEET_NO."))
  
  (setq SUPERLINK (LM:vl-getattributevalue (vlax-ename->vla-object main) "SUPERLINK"))
  (setq NAMEFILE (LM:vl-getattributevalue (vlax-ename->vla-object main) "NAMEFILE"))
  
  ; (setq DRAWING_NO2 (LM:vl-getattributevalue (vlax-ename->vla-object main) "DRAWING_NO2"))
  
  
  
  
  (setq mySet (ssget (list 
                      ;  (cons 8 "0") 
                       (cons 0 "INSERT") 
                      ;  (cons 2 "d2d")
                     ) 
              ) 
  )
  (setq entityCount (sslength mySet))
  
  (setq i 0)
  (while (< i entityCount) ; เมื่อลำดับยังไม่ถึง entityCount
      (setq ejc (ssname mySet i)) ; ดึง entity ที่ลำดับ i จาก mySet
      (setq o (vlax-ename->vla-object ejc))

      ; (setq entity1 (ssname mySet 1)) 
      ; (setq entity2 (ssname mySet 2))
      ; (setq entity3 (ssname mySet 0)) 
      ; (setq entity4 (ssname mySet 3)) 

      (setq o (vlax-ename->vla-object ejc))

  
      (LM:vl-setattributevalue o "PRELIM_NAME_PROJECT_1" NAME_PROJECT_1)
      (LM:vl-setattributevalue o "PRELIM_NAME_PROJECT_2" NAME_PROJECT_2)
      (LM:vl-setattributevalue o "PRELIM_NAME_PROJECT_3" NAME_PROJECT_3)
    
      (LM:vl-setattributevalue o "PRELIM_NAME_TITLE_1" NAME_TITLE_1)
      (LM:vl-setattributevalue o "PRELIM_NAME_TITLE_2" NAME_TITLE_2)
      (LM:vl-setattributevalue o "PRELIM_NAME_TITLE_3" NAME_TITLE_3)
    
      (LM:vl-setattributevalue o "DRAWING_NO2_NM" DRAWING_NO2)
      (LM:vl-setattributevalue o "TOTAL_SHEET_NO._NM" TOTAL_SHEET_NO.)
    

    
      (LM:vl-setattributevalue o "SUPERLINK" SUPERLINK)
      (LM:vl-setattributevalue o "NAMEFILE" NAMEFILE)
     
      ; (setq M_D (strcat "M10" (itoa (1+ i))))
      ; (LM:vl-setattributevalue o "FAC" M_D)
  
      ; เพิ่มลำดับ
      (setq i (1+ i))
  )
)
(defun c:R6R_TO_PRELIM_PROJECT_PART_PROJECT ()
  ;specify_with_BU_NOOM_ONLY
  (setq main (car (entsel "first pattern for copy")))
  ; (setq NAME_PROJECT_1 (LM:vl-getattributevalue (vlax-ename->vla-object main) "NAME_PROJECT_1"))
  ; (setq NAME_PROJECT_2 (LM:vl-getattributevalue (vlax-ename->vla-object main) "NAME_PROJECT_2"))
  ; (setq NAME_PROJECT_3 (LM:vl-getattributevalue (vlax-ename->vla-object main) "NAME_PROJECT_3"))
  
  (setq PRELIM_NAME_PROJECT_1 (LM:vl-getattributevalue (vlax-ename->vla-object main) "PRELIM_NAME_PROJECT_1"))
  (setq PRELIM_NAME_PROJECT_2 (LM:vl-getattributevalue (vlax-ename->vla-object main) "PRELIM_NAME_PROJECT_2"))
  (setq PRELIM_NAME_PROJECT_3 (LM:vl-getattributevalue (vlax-ename->vla-object main) "PRELIM_NAME_PROJECT_3"))

  (setq DRAWING_NO2_NM (LM:vl-getattributevalue (vlax-ename->vla-object main) "DRAWING_NO2_NM"))
  (setq TOTAL_SHEET_NO._NM (LM:vl-getattributevalue (vlax-ename->vla-object main) "TOTAL_SHEET_NO._NM"))
  
  (setq SUPERLINK (LM:vl-getattributevalue (vlax-ename->vla-object main) "SUPERLINK"))
  (setq NAMEFILE (LM:vl-getattributevalue (vlax-ename->vla-object main) "NAMEFILE"))
  
  ; (setq DRAWING_NO2 (LM:vl-getattributevalue (vlax-ename->vla-object main) "DRAWING_NO2"))
  
  
  
  
  (setq mySet (ssget (list 
                      ;  (cons 8 "0") 
                       (cons 0 "INSERT") 
                      ;  (cons 2 "d2d")
                     ) 
              ) 
  )
  (setq entityCount (sslength mySet))
  
  (setq i 0)
  (while (< i entityCount) ; เมื่อลำดับยังไม่ถึง entityCount
      (setq ejc (ssname mySet i)) ; ดึง entity ที่ลำดับ i จาก mySet
      (setq o (vlax-ename->vla-object ejc))

      ; (setq entity1 (ssname mySet 1)) 
      ; (setq entity2 (ssname mySet 2))
      ; (setq entity3 (ssname mySet 0)) 
      ; (setq entity4 (ssname mySet 3)) 

      (setq o (vlax-ename->vla-object ejc))

  
      (LM:vl-setattributevalue o "NAME_PROJECT_1" PRELIM_NAME_PROJECT_1)
      (LM:vl-setattributevalue o "NAME_PROJECT_2" PRELIM_NAME_PROJECT_2)
      (LM:vl-setattributevalue o "NAME_PROJECT_3" PRELIM_NAME_PROJECT_3)
    
      (LM:vl-setattributevalue o "PRELIM_NAME_TITLE_1" NAME_TITLE_1)
      (LM:vl-setattributevalue o "PRELIM_NAME_TITLE_2" NAME_TITLE_2)
      (LM:vl-setattributevalue o "PRELIM_NAME_TITLE_3" NAME_TITLE_3)
    
      (LM:vl-setattributevalue o "DRAWING_NO2" DRAWING_NO2_NM)
      (LM:vl-setattributevalue o "TOTAL_SHEET_NO." TOTAL_SHEET_NO._NM)
    

    
      (LM:vl-setattributevalue o "SUPERLINK" SUPERLINK)
      (LM:vl-setattributevalue o "NAMEFILE" NAMEFILE)
     
      ; (setq M_D (strcat "M10" (itoa (1+ i))))
      ; (LM:vl-setattributevalue o "FAC" M_D)
  
      ; เพิ่มลำดับ
      (setq i (1+ i))
  )
)



;TITTLE_BLOCK_AND_HEADING_COMMNAD_
  (defun c:SORTING_HEADING_SORH ()
    ;user_input_
      (setq PREFIX_NUM_ (getstring "Specify Prefix Number"))
      (setq START_NUM_i (getint "Specify Prefix Number"))
    ;
    ;selection_set
      (princ "Selection XX")
      (if  ;pre_select_ssget_or_post_select_ssget
        (= 
          (setq ss_pre_filter_set_xx_ (ssget "I" 
                                            (list 
                                              (cons 0 "INSERT") ;type of object
                                              ; (cons 8 "000 - GRID")   ;kind of layer
                                              ; (cons 2 "000-GRID_LINE_DYN")       ;kind of nameblock
                                              ; (cons 62 1)           ;kind of color call sign with color code index
                                            )
                                      )
          )
          nil
        )
        (progn 
          (setq ss_pre_filter_set_xx_ (ssget 
                                        (list 
                                          (cons 0 "INSERT") ;type of object
                                          ; (cons 8 "000 - GRID")   ;kind of layer
                                          ; (cons 2 "000-GRIDLINE_DYN")       ;kind of nameblock
                                          ; (cons 62 1)           ;kind of color call sign with color code index
                                        )
                                      )
          )
        )
        (sslength ss_pre_filter_set_xx_)
      )
    ;
    ;sorting_object_from_selection_
      (setq ATT_LIST_DATA_ (TA:standard_list_croodinate_sorting ss_pre_filter_set_xx_ "X" ))
    ;
    ;preloop_and_while
      (setq ATT_LIST_DATA_i 0)
      (while (< ATT_LIST_DATA_i (length ATT_LIST_DATA_))
        ;get_data
        (setq ATT_LIST_DATA_ename_ (car (nth  ATT_LIST_DATA_i ATT_LIST_DATA_)))
        (setq ATT_LIST_DATA_obj_ (vlax-ename->vla-object ATT_LIST_DATA_ename_))
        ;
        ;concat_data_
        
          (setq DRAWING_NO (strcat 
                   PREFIX_NUM_ 
                   (rtos START_NUM_i 2 0)
                 )
          )
        ;
        ;generate_data
          
          (LM:vl-setattributevalue ATT_LIST_DATA_obj_ "DRAWING_NO." DRAWING_NO)
        ;
        
        (setq START_NUM_i (+ START_NUM_i 1))
        (setq ATT_LIST_DATA_i (+ ATT_LIST_DATA_i 1))
      )
    ;
  )
  (defun c:MATCH_TITTLE_BLOCK_TO_HEADING ()
    ((setq TITTLE_BLOCK_ename_ (car (entsel "specify Object"))))
    (setq TITTLE_BLOCK_obj_ (vlax-ename->vla-object TITTLE_BLOCK_ename_))
    (LM:)
  )
;
