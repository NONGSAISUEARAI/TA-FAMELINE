; (defun c:qmsave ()
; ;   (setq FILEPATH (getvar "DWGPREFIX"))
; ;   (setq FILENAME (getvar "DWGNAME"))
; ;   (setq sum (strcat FILEPATH FILENAME))
; ;   (COMMAND "_SAVEAS" 
; ;           "2010"
; ;           sum
; ;           "Y"
; ;   )
; ;   ; (setq acadObj (vlax-get-acad-object))
; ;   ; (setq docs (vla-get-Documents acadObj))
; ;   ; (setq curDoc (vla-get-ActiveDocument acadObj))
; ;   ; (vla-Close curDoc :vlax-false)
; ;   ; (vla-Close curDoc )
; ;   ; (command "quit" "n" )
; ;   (command "close")

; )

; (c:qmsave)

;(alert "TA:AUTOMATION TEST")
